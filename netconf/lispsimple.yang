module lispsimple {
  namespace "urn:ietf:params:xml:ns:yang:lispsimple";
  prefix lispsimple;

  import ietf-inet-types {
    prefix inet;
  }

  organization "IETF LISP (Locator/ID Separation Protocol) Working Group";
  contact "lisp@ietf.org";
  description
    "This YANG module defines the generic configuration
     data for LISP. The module can be extended by vendors 
     to define vendor-specific LISP configuration 
     parameters and policies.
     
     Copyright (c) 2015 IETF Trust and the persons identified as
     authors of the code.  All rights reserved.
     
     Redistribution and use in source and binary forms, with or
     without modification, is permitted pursuant to, and subject
     to the license terms contained in, the Simplified BSD License
     set forth in Section 4.c of the IETF Trust's Legal Provisions
     Relating to IETF Documents
     (http://trustee.ietf.org/license-info).
     
     This version of this YANG module is part of RFC 6338; see
     the RFC itself for full legal notices.
     
    ";

  revision 2015-07-02 {
    description
      "LISPmob revision.";
  }
    
  typedef eid-id {
    type string;
  }
    
  typedef simple-address {
    type union {
      type inet:ip-address;
    }
  }
    
    
  grouping lcaf-address {
    leaf lcaf-type {
      type enumeration {
        enum "null";
        enum "afi-list";
        enum "instance-id";
        enum "as-number";
        enum "application-data";
        enum "geo-coordinates";
        enum "opaque-key";
        enum "nat-ttraversal";
        enum "nonce-locator";
        enum "multicast-info";
        enum "explicit-locator-path";
        enum "security-key";
        enum "source-dest-key";
        enum "replication-list";
        enum "json-data-model";
        enum "key-value-address";
        enum "encapsulation-format";
      }
    }
    choice address {
      container explicit-locator-path {
        when "lcaf-type = explicit-locator-path";
        list hop {
          key "address";
          leaf address {
            type simple-address;
          }
          leaf lrs-bits {
            type bits {
              bit lookup;
              bit rloc-probe;
              bit strict;
            }
          }
        }
      }
    }
  }  
    
  grouping lisp-address {
    leaf afi {
      type enumeration {
        enum "ipv4" {
          value 1;
        }
        enum "ipv6" {
          value 2;
        }
        enum "lcaf" {
          value 16387;
        }
      }
    }
    leaf instance-id {
      type instance-id-type;
    }
    choice address {
      case ipv4 {
        when "afi = ipv4";
        leaf ipv4 {
          type inet:ipv4-address;
        }
      }
      case ipv6 {
        when "afi = ipv6";
        leaf ipv6 {
          type inet:ipv6-address;
        }
      }
      case lcaf {
        when "afi = lcaf";
        container lcaf {
          uses lcaf-address;
        }
      }
    }
    leaf mask {
      type uint8;
    }
  }

  typedef interface-name {
    description
      "Name of a device interface";
    type string;
  }
    
  typedef map-reply-action {
    description
      "Defines the lisp map-cache ACT type";
    type enumeration {
      enum "no-action" {
        value 0;
      }
      enum "natively-forward" {
        value 1;
      }
      enum "send-map-request" {
        value 2;
      }
      enum "drop" {
        value 3;
      }
    }
  }
    
  typedef instance-id-type {
    type uint32 {
      range "0..16777214";
    }
  }
   
  typedef auth-key-type {
    type enumeration {
      enum "none" {
        value 0;
      }
      enum "hmac-sha-1-96" {
        value 1;
      }
      enum "hmac-sha-256-128" {
        value 2;
      }
    }
  }
   

  grouping locators {
    list rloc {
      key "name";
      leaf name {
        type string;
      }
      choice address-type {
        case interface-address {
          leaf interface {
            type interface-name;
          }
        }
        case lisp-address {
          container locator-address {
            uses lisp-address;
          }
        }
      }
      leaf priority {
        type uint8;
      }
      leaf weight {
        type uint8;
      }
      leaf multicast-priority {
        type uint8;
      }
      leaf multicast-weight {
        type uint8;
      }
    }
  }
    
  grouping mappings {
    list mapping {
      key "id";
      leaf id {
        type eid-id;
      }
      container eid {
        uses lisp-address;
      }
      leaf ttl {
        type uint32;
      }
      choice locator-list {
        case negative-mapping {
          leaf map-reply-action {
            type map-reply-action;
          }
        }
        case positive-mapping {
          container rlocs {
            uses locators;
          }
        }
        default "positive-mapping";
      }
    }
  }
    
  container itr-cfg {
    container rloc-probing {
      presence "RLOC probing active";
      leaf interval {
        type uint16;
        units "seconds";
        description
          "Interval in seconds";
      }
      leaf retries {
        type uint8;
        description
          "Number of retries";
      }
      leaf retries-interval {
        type uint16;
        units "seconds";
        description
          "Interval in seconds between retries";
      }
    }
    
    container itr-rlocs {
      description
        "List of RLOCs of the ITR included in Map-Requests";
      list itr-rloc {
        key "id";
        leaf id {
          type string;
        }
        container address {
          uses lisp-address;
        }
      }
    }
    
    container map-resolvers {
      list map-resolver {
        key "id";
        leaf id {
          type eid-id;
        }
        leaf-list map-resolver-address {
          type inet:ip-address;
        }
      }
    }
    
    container proxy-etrs {
      list proxy-etr {
        key "id";
        leaf id {
          type eid-id;
        }
        container eid-address {
          uses lisp-address;
        }
        leaf-list proxy-etr-address {
          type inet:ip-address;
        }
      }
    }
   
    container map-cache {
      uses mappings {
        augment "mapping" {
          leaf static {
            description
              "A configured mapping is a static mapping. If the mapping
               is learned, it is operational data and static is false.";
            type boolean;
            default "true";
          }
        }
      }
    }
  }  
  container etr-cfg {
   
    container map-servers {
      list map-server {
        key "address";
        leaf address {
          type inet:ip-address;
        }
        leaf auth-key {
          type string;
        }
        leaf auth-key-type {
          type auth-key-type;
        }
        
      }
      leaf proxy-reply {
        type boolean;
      }
    }           
  
    container local-eids {
      list local-eid {
        key "id";
        leaf id {
          type eid-id;
        }
        container eid-address {
          uses lisp-address;
        }

        container rlocs {
          uses locators;
        }
        leaf record-ttl {
          type uint32;
        }
      }
    }
  }
  container rtr-cfg {
    container map-resolvers {
      list map-resolver {
        key "id";
        leaf id {
          type eid-id;
        }
        leaf-list map-resolver-address {
          type inet:ip-address;
        }
      }
    }
  }
}
